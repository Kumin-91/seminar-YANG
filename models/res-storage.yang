module res-storage {
    yang-version 1.1;
    namespace "urn:csmin:params:xml:ns:yang:res-storage";
    prefix rs;

    grouping resource-storage {
        container storage {

            leaf s3-endpoint {
                type string;
                mandatory true;
                description "S3 호환 저장소(MinIO)의 엔드포인트 도메인 (예: bucket.example.com)";
            }
            leaf s3-access-key {
                type string;
                mandatory true;
                description "S3 호환 저장소 (MinIO)의 액세스 키";
            }
            leaf s3-secret-key {
                type string;
                mandatory true;
                description "S3 호환 저장소 (MinIO)의 시크릿 키";
            }

            leaf redis-endpoint {
                type string;
                mandatory true;
                description "메타데이터 관리를 위한 Redis 엔드포인트 (예: 100.100.2.200)";
            }
            leaf redis-password { 
                type string; 
                mandatory true;
                description "Redis 접속 비밀번호";
            }

            leaf cache-size {
                type uint32;
                mandatory true;
                units "GB";
                description "로컬 NVMe/SSD 캐시 할당량 (GB 단위)";
            }
        }
    }
}
