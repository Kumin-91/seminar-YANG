module res-network {
    yang-version 1.1;
    namespace "urn:csmin:params:xml:ns:yang:res-network";
    prefix rn;

    import common-types { prefix ct; }
    import ietf-inet-types { prefix inet; }

    grouping resource-network {
        container network {
            leaf ssh-user {
                type string;
                mandatory true;
                description "SSH 접속에 사용할 사용자 이름";
            }
            leaf ssh-port {
                type inet:port-number;
                mandatory true;
                description "SSH 접속에 사용할 포트 번호";
            }
            choice bootstrap-strategy {
                mandatory true;
                case aws-strategy {
                    when "../compute/platform = 'aws'";
                    leaf public-ip-required {
                        type boolean;
                        default true;
                        description "AWS 노드 부트스트랩 시 퍼블릭 IP 할당 여부";
                    }
                    leaf use-eip {
                        type boolean;
                        default false;
                        description "AWS 노드 부트스트랩 시 고정 IP 사용 여부";
                    }
                }
                case on-premise-strategy {
                    when "../compute/platform = 'on-premise'";
                    leaf bootstrap-ip {
                        type inet:ip-address;
                        mandatory true;
                        description "온프레미스 노드 부트스트랩에 사용할 IP 주소";
                    }
                }
            }
        }
    }
}
