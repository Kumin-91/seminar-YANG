module aws-provider {
    yang-version 1.1;
    namespace "urn:hybrid:aws-provider";
    prefix aws;

    import ietf-inet-types { prefix inet; }

    container aws-config {
        leaf region {
            type string {
                pattern 'ap-northeast-[1-3]';
            }
            default "ap-northeast-2";
            description "동북아시아 AWS 리전 (예: ap-northeast-2)";
        }

        leaf vpc-cidr {
            type inet:ipv4-prefix;
            default "10.30.0.0/16";
            must "number(substring-after(current(), '/')) >= 16 and " + 
                 "number(substring-after(current(), '/')) <= 28" {
                error-message "AWS VPC CIDR prefix length must be between 16 and 28.";
            }
            description "VPC의 CIDR 블록";
        }

        leaf public-subnet-cidr {
            type inet:ipv4-prefix;
            default "10.30.1.0/24";
            must "number(substring-after(current(), '/')) >= number(substring-after(../vpc-cidr, '/')) and " +
                 "number(substring-after(current(), '/')) <= 28" {
                error-message "Subnet mask must be narrower than or equal to VPC mask.";
            }
        }

        leaf private-subnet-cidr {
            type inet:ipv4-prefix;
            default "10.30.2.0/24";
            must "number(substring-after(current(), '/')) >= number(substring-after(../vpc-cidr, '/')) and " +
                 "number(substring-after(current(), '/')) <= 28" {
                error-message "Subnet mask must be narrower than or equal to VPC mask.";
            }
        }
    }
}
