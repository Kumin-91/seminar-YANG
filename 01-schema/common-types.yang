module common-types {
    yang-version 1.1;
    namespace "urn:csmin:params:xml:ns:yang:common-types";
    prefix ct;

    typedef node-platform {
        type enumeration {
            enum aws;
            enum on-premise;
        }
    }
    typedef cpu-arch {
        type enumeration {
            enum x86_64;
            enum arm64;
        }
    }
    typedef aws-instance-type {
        type string {
            /* 구조 분석:
                1. [tcrm]: 인스턴스 패밀리
                2. [1-8]: 세대 번호
                3. [gai]?: 프로세서 (g:Graviton, a:AMD, i:Intel) - 생략 시 인텔/표준
                4. [dbn]*: 부가 기능 (d:Disk, b:EBS, n:Network)
                5. \.(nano|micro|small|medium): 인스턴스 사이즈
            */
            pattern '[tcrm][1-8][gai]?[dbn]*\.(nano|micro|small|medium)';
        }
    }
    typedef k3s-role {
        type enumeration {
            enum server;
            enum agent;
        }
    }
    typedef node-role {
        type enumeration {
            enum primary;
            enum secondary;
            enum fallback;
        }
    }
}
