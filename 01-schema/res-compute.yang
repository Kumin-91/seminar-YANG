module res-compute {
    yang-version 1.1;
    namespace "urn:csmin:params:xml:ns:yang:res-compute";
    prefix rc;

    import common-types { prefix ct; }

    grouping resource-compute {
        container compute {
            leaf platform {
                type ct:node-platform;
                mandatory true;
            }
            leaf arch {
                type ct:cpu-arch;
                mandatory true;
            }
            choice platform-spec {
                mandatory true;
                case aws {
                    when "platform = 'aws'";
                    leaf instance-type {
                        type ct:aws-instance-type;

                        must "(../arch = 'arm64' and re-match(., '[tcrm][1-8]g.*')) or " + 
                             "(../arch = 'x86_64' and not(re-match(., '[tcrm][1-8]g.*')))" {
                            error-message "Architecture mismatch detected: 'arm64' platform requires 'g' instance types, while 'x86_64' platform cannot use 'g' instance types.";
                        }

                        mandatory true;
                        description "AWS 인스턴스 유형 (예: t4g.medium)";
                    }
                    leaf ebs-size {
                        type uint16;
                        units "GB";
                        mandatory true;
                        description "AWS EBS 볼륨 크기 (GB 단위)";
                    }
                }
                case on-premise {
                    when "platform = 'on-premise'";
                    leaf vcpu {
                        type uint8 { range "1..8"; }
                        mandatory true;
                        description "가상 CPU 코어 수";
                    }
                    leaf memory {
                        type uint8 { range "1..16"; }
                        units "GB";
                        mandatory true;
                        description "메모리 크기 (GB 단위)";
                    }
                }
            }
        }
    }
}
