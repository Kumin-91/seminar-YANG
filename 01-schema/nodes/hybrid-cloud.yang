module hybrid-cloud {
    yang-version 1.1;
    namespace "urn:csmin:params:xml:ns:yang:hybrid-cloud";
    prefix hc;

    import common-types { prefix ct; }
    import res-compute { prefix rc; }
    import res-network { prefix rn; }
    import res-storage { prefix rs; }

    container cluster {
        list node {
            key "name";
            description "클러스터를 구성하는 개별 노드 정보";
            leaf name { 
                type string; 
                description "클러스터 이름";
            }
            // After - Kubernetes 구조에 맞게 일반화
            container k8s-role-assignment {
                description "이 노드가 수행하는 Kubernetes 역할과 그 부트스트랩 전략";
                leaf node-role {
                    type ct:k8s-node-role;
                    description "Kubernetes 역할";
                }
                leaf bootstrap-role {
                    type ct:k8s-bootstrap-role;
                    must "not(../node-role = 'worker' and . = 'init')" {
                        error-message "'worker' node cannot have 'init' bootstrap role.";
                    }
                    description "부트스트랩 전략";
                }
            }

            // grouping으로 정의된 각 리소스 구성 요소
            uses rc:resource-compute;
            uses rn:resource-network;
            uses rs:resource-storage;
        }
    }
}
