module hybrid-cloud {
    yang-version 1.1;
    namespace "urn:csmin:params:xml:ns:yang:hybrid-cloud";
    prefix hc;

    import common-types { prefix ct; }
    import res-compute { prefix rc; }
    import res-network { prefix rn; }
    import res-storage { prefix rs; }

    container cluster {
        list node {
            key "name";
            leaf name { type string; }
            // k3s 역할별 우선순위 정의
            list role-assignment {
                key "role";
                description "이 노드가 수행하는 기술적 역할과 그 전략적 중요도";
                leaf role {
                    type ct:k3s-role; // server, agent
                    description "기술적 역할 (Server 또는 Agent)";
                }
                leaf priority {
                    type ct:node-role;
                    mandatory true;
                    description "해당 역할이 클러스터 내에서 갖는 전략적 우선순위";
                }
            }   
            // grouping으로 정의된 각 리소스 구성 요소
            uses rc:resource-compute;
            uses rn:resource-network;
            uses rs:resource-storage;
        }
    }
}
