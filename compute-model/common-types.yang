module common-types {
    yang-version 1.1;
    namespace "urn:csmin:params:xml:ns:yang:common-types";
    prefix ct;

    typedef cpu-arch {
        type enumeration {
            enum x86_64;
            enum arm64;
        }
    }

    typedef k3s-role {
        type enumeration {
            enum server;
            enum agent;
        }
    }

    typedef node-role {
        type enumeration {
            enum primary;
            enum secondary;
            enum fallback;
        }
    }
}
